FME workspace 2_CityGMLtoIndoorGML_v4.fmw
Title: CityGML psADE to IndoorGML ps extension
Description: CityGML psADE to IndoorGML ps extension
Convert from CityGML 2.0 psADE to IndoorGML 1.03 ps extension for OGC Indoor GML pilot
Requires 
- FME 2019.01 b19253 or later
- ADE-PublicSafety-ver03_1_2.xsd for CityGML ADE
- indoorgmlpsextention.xsd for IndoorGML app schema extension
History: Nov 30, 2018,Dean Hintz,Created v1.0,Jan 8, 2019,Dean,Updated for latest CityGML ps ADE,Mar 5, 2019,Dean,Imported schema from indoorgmlpsextention.xsd,Mar 5, 2019,Dean,Changed core.CellSpaces to navi.GeneralSpaces in order to store room usage and function information,Mar 8, 2019,Dean,Added ConnectionBoundary for doors,Mar 9, 2019,Dean,Changed transitions to connect rooms via doors - simplistic neighbor based navigation for testing only. Corrected former misinterpretation of transitions as doors - transitions connect states as nav lines, connection boundaries are doors,Mar 10. 2019,Dean,Updated docs,Apr 15, 2019,Dean,Added bldg:intBuildingFurniture and bldg:POI , updated to latest ade 1.1,Apr 20, 2019,Dean,Added new ps feature types for PublicSafetyBuildingFurniture and Medical,Apr 25, 2019,Dean,Major refactoring to handle different geometry model interpretation from KU Central Plaza citygml,June 11, 2019,Dean,Rework to handle latest psADE 3.1.2, enumeration types, ps rooms, ps doors,June 11, 2019,Dean,Ran on Hancock dataset

Parameters:
- DestDataset_INDOORGML =
- SourceDataset_CITYGML =

Readers:
- CITYGML_1: CITYGML from $(SourceDataset_CITYGML)

Writers:
- INDOORGML_1: INDOORGML to $(DestDataset_INDOORGML)

core_CityModel (reader CITYGML_1)
    attributes: citygml_target_uri xml_buffer, gml_description xml_buffer, gml_name xml_buffer, citygml_city_object_member{}.xlink_href xml_buffer, gml_feature_member{}.xlink_href xml_buffer, citygml_appearance_member{}.xlink_href xml_buffer
    -> AttributeCreator_7
bldg_Room (reader CITYGML_1)
    attributes: citygml_bounded_by{}.xlink_href xml_buffer, citygml_class xml_buffer, citygml_class_codeSpace xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_interior_furniture{}.xlink_href xml_buffer, citygml_level_of_detail{} xml_buffer, citygml_relative_to_terrain xml_char(33), citygml_relative_to_water xml_char(38), citygml_room_installation{}.xlink_href xml_buffer, citygml_target_uri xml_buffer, citygml_terminationDate xml_date, citygml_usage{} xml_buffer, citygml_usage{}.codeSpace xml_buffer, externalReference{}.externalObject.name xml_xml, externalReference{}.externalObject.uri xml_xml, externalReference{}.informationSystem xml_xml, gml_description xml_buffer, gml_name xml_buffer, citygml_appearance{}.xlink_href xml_buffer
    -> AppearanceRemover_2
bldg_Door (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_address{}.xlink_href xml_buffer, citygml_appearance{}.xlink_href xml_buffer
    -> AttributeCreator_3

Bookmark: General prep
AttributeCreator_7
    ATTR_TABLE:
      SET_TO primalSpaceFeatures.nilReason = unknown
      SET_TO multiLayeredGraph.nilReason = unknown
      SET_TO gml_id = IF_500
      SET_TO xml_ns_uri = http://www.opengis.net/indoorgml/1.0/core
    -> IndoorFeatures
    -> AttributeCreator_2
    -> AttributeCreator_MultiLayeredGraph
AppearanceRemover_2
    SIDE_TO_REMOVE = Front and Back Sides
    -> AttributeCreator

Bookmark: Generate IndoorFeature and PrimalSpaceFeature Container Features
IndoorFeatures: Logger
    LOG_FEATURE = LOG_ONLY
    MAXCOORDS = 20
    MAXFEATS = 20
    MESSAGE = Feature is:
    SEVERITY = INFO
    LOGGED -> IndoorFeatures (writer INDOORGML_1)
AttributeCreator_2
    ATTR_TABLE:
      SET_TO gml_parent_id = @Value(gml_id)
      SET_TO gml_parent_property = primalSpaceFeatures
      SET_TO gml_id = PSF_@Value(gml_id)
    -> AttributeCreator_9
AttributeCreator_9
    ATTR_TABLE:
      SET_TO duality.nilReason = unknown
      SET_TO partialboundedBy{0}.nilReason = unknown
      SET_TO gml_metaDataProperty{0}.nilReason = unknown
      SET_TO gml_description.nilReason = unknown
    -> Counter_2
Counter_2
    CNT_ATTR = gml_name{0}
    DOMAIN = counter
    SCOPE = Global
    START = 101
    -> PrimalSpaceFeatures
PrimalSpaceFeatures: Logger
    LOG_FEATURE = LOG_ONLY
    MAXCOORDS = 20
    MAXFEATS = 20
    MESSAGE = Feature is:
    SEVERITY = INFO
    LOGGED -> PrimalSpaceFeatures (writer INDOORGML_1)

Bookmark: IndoorGML FeatureTypes
IndoorFeatures (writer INDOORGML_1)
    attributes: primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer
PrimalSpaceFeatures (writer INDOORGML_1)
    attributes: duality.nilReason xml_char(200), partialboundedBy{}.nilReason xml_char(200), gml_metaDataProperty{}.nilReason xml_char(200), gml_description.nilReason xml_char(200), primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer, gml_name{0} xml_int64
SpaceLayer (writer INDOORGML_1)
    attributes: spaceLayerMember{}.nilReason xml_char(200), primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer
edges (writer INDOORGML_1)
    attributes: stateMember{}.nilReason xml_char(200), spaceLayerMember{}.nilReason xml_char(200), primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer
nodes (writer INDOORGML_1)
    attributes: stateMember{}.nilReason xml_char(200), owns xml_char(200), spaceLayerMember{}.nilReason xml_char(200), primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer
spaceLayers (writer INDOORGML_1)
    attributes: spaceLayerMember{}.nilReason xml_char(200), primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer
MultiLayeredGraph (writer INDOORGML_1)
    attributes: duality.nilReason xml_char(200), partialboundedBy{}.nilReason xml_char(200), gml_metaDataProperty{}.nilReason xml_char(200), gml_description.nilReason xml_char(200), primalSpaceFeatures.nilReason xml_char(200), multiLayeredGraph.nilReason xml_char(200), citygml_target_uri xml_buffer, gml_description xml_buffer, gml_name xml_buffer, citygml_city_object_member{}.xlink_href xml_buffer, gml_feature_member{}.xlink_href xml_buffer, citygml_appearance_member{}.xlink_href xml_buffer, gml_name{0} xml_int64
ConnectionSpace (writer INDOORGML_1)
    attributes: gml_description xml_buffer, gml_name xml_buffer
Transition (writer INDOORGML_1)
    attributes: gml_description xml_buffer, gml_name xml_buffer
State (writer INDOORGML_1)
    attributes: gml_id0 xml_buffer, duality.xlink_href xml_char(200), duality.nilReason xml_char(200), partialboundedBy{}.nilReason xml_char(200), gml_metaDataProperty{}.nilReason xml_char(200), gml_description xml_buffer, class xml_char(200), PSRoomType xml_char(200), usage xml_char(200), function xml_char(200), gml_name xml_buffer, citygml_appearance{}.xlink_href xml_buffer, partialboundedBy{}.xlink_href xml_char(200), xlink_href xml_char(200), citygml_address{}.xlink_href xml_buffer
TransitionSpace (writer INDOORGML_1)
    attributes: gml_description xml_buffer, gml_name xml_buffer
GeneralSpace (writer INDOORGML_1)
    attributes: gml_description xml_buffer, gml_name xml_buffer
ConnectionBoundary (writer INDOORGML_1)
    attributes: partialboundedBy{}.nilReason xml_char(200), gml_metaDataProperty{}.nilReason xml_char(200), citygml_address{}.xlink_href xml_buffer, citygml_appearance{}.xlink_href xml_buffer, Face_list{}.gml_id xml_buffer, _overlaps xml_uint32, gml_id1 xml_char(200)

Bookmark: Generate MultiLayerGraph Container Features
AttributeCreator_MultiLayeredGraph
    ATTR_TABLE:
      SET_TO gml_parent_id = @Value(gml_id)
      SET_TO gml_parent_property = multiLayeredGraph
      SET_TO xml_ns_uri = http://www.opengis.net/indoorgml/1.0/core
      SET_TO gml_id = MG_@Value(gml_id)
    -> AttributeCreator_10
    -> AttributeCreator_spaceLayerMember
AttributeCreator_spaceLayerMember
    ATTR_TABLE:
      SET_TO gml_parent_id = @Value(gml_id)
      SET_TO gml_parent_property = MultiLayeredGraph
      SET_TO gml_id = SLs_@Value(gml_id)
      SET_TO spaceLayerMember{0}.nilReason = unknown
    -> SpaceLayers
    -> AttributeCreator_SpaceLayer
AttributeCreator_SpaceLayer
    ATTR_TABLE:
      SET_TO gml_parent_id = @Value(gml_id)
      SET_TO gml_parent_property = spaceLayerMember
      SET_TO gml_id = SL_@Value(gml_id)
    -> SpaceLayer
    -> AttributeCreator_nodes
    -> AttributeCreator_edges
SpaceLayer: Logger
    LOG_FEATURE = LOG_ONLY
    MAXCOORDS = 20
    MAXFEATS = 20
    MESSAGE = Feature is:
    SEVERITY = INFO
    LOGGED -> SpaceLayer (writer INDOORGML_1)
AttributeCreator_edges
    ATTR_TABLE:
      SET_TO gml_parent_id = @Value(gml_id)
      SET_TO gml_id = E_@Value(gml_id)
      SET_TO stateMember{0}.nilReason = unknown
      SET_TO gml_parent_property = SpaceLayer
    -> edges (writer INDOORGML_1)
AttributeCreator_nodes
    ATTR_TABLE:
      SET_TO gml_parent_id = @Value(gml_id)
      SET_TO gml_id = N_@Value(gml_id)
      SET_TO stateMember{0}.nilReason = unknown
      SET_TO gml_parent_property = SpaceLayer
      SET_TO owns = false
    -> AttributeCreator_11_Output
AttributeCreator_11_Output: Logger
    LOG_FEATURE = LOG_ONLY
    MAXCOORDS = 20
    MAXFEATS = 20
    MESSAGE = Node Feature is:
    SEVERITY = INFO
    LOGGED -> nodes (writer INDOORGML_1)
SpaceLayers: Logger
    LOG_FEATURE = LOG_ONLY
    MAXCOORDS = 20
    MAXFEATS = 20
    MESSAGE = Feature is:
    SEVERITY = INFO
    LOGGED -> spaceLayers (writer INDOORGML_1)
AttributeCreator_10
    ATTR_TABLE:
      SET_TO duality.nilReason = unknown
      SET_TO partialboundedBy{0}.nilReason = unknown
      SET_TO gml_metaDataProperty{0}.nilReason = unknown
      SET_TO gml_description.nilReason = unknown
    -> Counter_3
Counter_3
    CNT_ATTR = gml_name{0}
    DOMAIN = counter
    SCOPE = Global
    START = 101
    -> MultiLayeredGraph
MultiLayeredGraph: Logger
    LOG_FEATURE = LOG_ONLY
    MAXCOORDS = 20
    MAXFEATS = 20
    MESSAGE = Feature is:
    SEVERITY = INFO
    LOGGED -> MultiLayeredGraph (writer INDOORGML_1)

Bookmark: Generate Geometry
AttributeCreator
    ATTR_TABLE:
      SET_TO gml_parent_id = PSF_IF_500
      SET_TO gml_parent_property = cellSpaceMember
      SET_TO gml_id0 = @Value(gml_id)
      SET_TO gml_id = GS_@Value(gml_id)
    -> GeometryCoercer
GeometryCoercer
    GQUERY:
      for $geom in //geometry
      where $geom/count(parent::geometry) = 0
      return number($geom/@fme_id)
    KIND = fme_brep_solid
    COERCED -> GeometryPropertySetter_2
    UNTOUCHED -> GeometryPropertySetter_2
GeometryPropertySetter_2
    GQUERY:
      for $geom in //geometry
      where $geom/@fme_geometry_type = 'IFMEBRepSolid'
      return number($geom/@fme_id)
    OVERWRITE_CHOICE = No
    REMOVE_ATTRIBUTE = No
    SETTYPE_PARAM = Traits From Attributes
    SRC_ATTRS = gml_id
    SET -> GeometryPropertySetter
GeometryPropertySetter
    GEOM_NAME_FIELD = cellSpaceGeometry.Geometry3D
    OVERWRITE_CHOICE = Yes
    SETTYPE_PARAM = Geometry Name
    SET -> AttributeCreator_Room

Bookmark: Schema Mapping
AttributeCreator_Room
    ATTR_TABLE:
      SET_TO gml_id = CS_@Value(gml_id0)
      SET_TO duality.nilReason = unknown
      SET_TO partialboundedBy{0}.nilReason = unknown
      SET_TO gml_metaDataProperty{0}.nilReason = unknown
      SET_TO gml_description = @Value(gml_description)
      SET_TO class = 1020
      SET_TO PSRoomType = unknown
      SET_TO usage = 2550
      SET_TO function = 2550
    -> GeometryCoercer_3
    -> FeatureJoiner_7 [RIGHT]
    -> FeatureJoiner_6 [RIGHT]
    -> FeatureJoiner_8 [LEFT]

Bookmark: Generate Geometry
AttributeCreator_3
    ATTR_TABLE:
      SET_TO gml_parent_id = PSF_IF_500
      SET_TO gml_parent_property = cellSpaceMember
      SET_TO gml_id0 = @Value(gml_id)
      SET_TO gml_id = GS_@Value(gml_id)
    -> GeometryCoercer_2
GeometryCoercer_2
    GQUERY:
      for $geom in //geometry
      where $geom/count(parent::geometry) = 0
      return number($geom/@fme_id)
    KIND = fme_brep_solid
    COERCED -> GeometryPropertySetter_4
    UNTOUCHED -> GeometryPropertySetter_4
GeometryPropertySetter_4
    GQUERY:
      for $geom in //geometry
      where $geom/@fme_geometry_type = 'IFMEBRepSolid'
      return number($geom/@fme_id)
    OVERWRITE_CHOICE = No
    REMOVE_ATTRIBUTE = No
    SETTYPE_PARAM = Traits From Attributes
    SRC_ATTRS = gml_id
    SET -> GeometryPropertySetter_3
GeometryPropertySetter_3
    GEOM_NAME_FIELD = cellSpaceGeometry.Geometry3D
    OVERWRITE_CHOICE = Yes
    SETTYPE_PARAM = Geometry Name
    SET -> AttributeCreator_Door

Bookmark: Schema Mapping
AttributeCreator_Door
    ATTR_TABLE:
      SET_TO gml_id = CS_@Value(gml_id0)
      SET_TO duality.nilReason = unknown
      SET_TO partialboundedBy{0}.nilReason = unknown
      SET_TO gml_metaDataProperty{0}.nilReason = unknown
      SET_TO gml_description = @Value(gml_description)
      SET_TO class = 1020
      SET_TO PSRoomType = unknown
      SET_TO usage = 2550
      SET_TO function = 2550
      SET_TO xlink_href = unknown
    -> FeatureJoiner_4 [RIGHT]
    -> GeometryCoercer_3
    -> FeatureJoiner_5 [LEFT]
    -> FeatureJoiner_3 [RIGHT]

Bookmark: Lista de espacios adyacentes
GeometryCoercer_3
    GQUERY:
      for $geom in //geometry
      where $geom/count(parent::geometry) = 0
      return number($geom/@fme_id)
    KIND = fme_composite_surface
    COERCED -> SurfaceOnSurfaceOverlayer [SURFACE]
SurfaceOnSurfaceOverlayer
    ACCUM_ATTRS_NAME = Merge Incoming Attributes
    DEAGGREGATE_INPUT = Yes
    ENABLE_TOLERANCE = Yes
    LIST_ATTRS_TO_INCLUDE = gml_id
    LIST_NAME = Face_list
    NORMAL_TOLERANCE = 1
    OFFSET_TOLERANCE = 0.01
    OVC_ATTR = _overlaps
    SURFACE -> AttributeFilter
AttributeFilter
    ATTR_NAME = _overlaps
    ATTR_VALUES = <Empty>,<Missing>,<Null>,<Unfiltered>,2
    2 -> CRCCalculator
CRCCalculator
    ALG_CHOICES = CRC-32
    CRC_ATTR = _edge_id
    CRC_TYPE = GEOM_ENCODED
    -> FeatureJoiner_6 [LEFT]
    -> FeatureJoiner_4 [LEFT]
    -> FeatureJoiner_3 [LEFT]
    -> FeatureJoiner_7 [LEFT]
    -> AttributeCreator_15
    -> FeatureJoiner_9 [LEFT]

Bookmark: Transition
AttributeCreator_15
    ATTR_TABLE:
      SET_TO GML_ID_INICIO = @Value(Face_list{0}.gml_id)
      SET_TO GML_ID_FINAL = @Value(Face_list{1}.gml_id)
    -> FeatureJoiner_11 [RIGHT]
    -> FeatureJoiner_12 [RIGHT]
FeatureJoiner_11
    ATTR_CONFLICT_RES = Use Left
    GEOMETRY_HANDLING = Use Left
    JOIN_KEYS = gml_id0 GML_ID_INICIO AUTO
    JOIN_MODE = Inner
    JOINED -> CoordinateExtractor
CoordinateExtractor
    IND = 0
    MODE = Specify Coordinate
    X_ATTR = Inicio_x
    Y_ATTR = Inicio_y
    Z_ATTR = Inicio_z
    -> FeatureMerger [REQUESTOR]
FeatureJoiner_12
    ATTR_CONFLICT_RES = Use Left
    GEOMETRY_HANDLING = Use Left
    JOIN_KEYS = gml_id0 GML_ID_FINAL AUTO
    JOIN_MODE = Inner
    JOINED -> CoordinateExtractor_2
CoordinateExtractor_2
    IND = 0
    MODE = Specify Coordinate
    X_ATTR = Fin_x
    Y_ATTR = Fin_y
    Z_ATTR = Fin_z
    -> FeatureMerger [SUPPLIER]
FeatureMerger
    ATTR_ACCUM_MODE = Merge Supplier
    ATTR_CONFLICT_RES = Use Requestor
    IGNORE_NULLS = No
    JOIN_KEYS = @Value(_edge_id) @Value(_edge_id) AUTO
    MERGE_TYPE = Attributes Only
    PROCESS_DUPS = NO
    REJECT_NULL_MISSING_KEYS = No
    SUPPLIERS_FIRST = No
    MERGED -> VertexCreator
Note: VertexCreator [VertexCreator] / Parameters: / Mode: Replace with Point / X Value: @Value(Inicio_x) / Y Value: @Value(Inicio_y) / Z Value: @Value(Inicio_z)
VertexCreator
    MODE_NAME = Replace with Point
    XVAL = @Value(Inicio_x)
    YVAL = @Value(Inicio_y)
    ZVAL = @Value(Inicio_z)
    -> VertexCreator_3
Note: VertexCreator_3 [VertexCreator] / Parameters: / Mode: Add Point / X Value: @Value(Fin_x) / Y Value: @Value(Fin_y) / Z Value: @Value(Fin_z)
VertexCreator_3
    MODE_NAME = Add Point
    XVAL = @Value(Fin_x)
    YVAL = @Value(Fin_y)
    ZVAL = @Value(Fin_z)
    -> AttributeCreator_16
AttributeCreator_16
    ATTR_TABLE:
      SET_TO gml_parent_id = E_SL_SLs_MG_IF_500
      SET_TO gml_parent_property = transitionMember
      SET_TO gml_id0 = @Value(gml_id)
      SET_TO gml_id = T_@Value(GML_ID_INICIO)_to_@Value(GML_ID_FINAL)
      SET_TO xml_ns_uri = http://www.opengis.net/indoorgml/1.0/core
      SET_TO fme_geometry = fme_line
      SET_TO weight = 1
      SET_TO fme_type = fme_line
      SET_TO xml_type = xml_line
      SET_TO connects{0}.xlink_href = S_@Value(GML_ID_INICIO)
      SET_TO connects{1}.xlink_href = S_@Value(GML_ID_FINAL)
    -> AttributeRemover_2
AttributeRemover_2
    LIST_ATTRS = Face_list{} Face_list{}.NodoFinal Face_list{}.NodoInicial citygml_address{} citygml_address{}.xlink_href citygml_appearance{}.xlink_href gml_metaDataProperty{} gml_metaDataProperty{}.nilReason gml_name{} partialboundedBy{} partialboundedBy{}.nilReason partialboundedBy{}.xlink_href
    REMOVE_ATTRS = citygml_appearance{0}.xlink_href,Face_list{0}.NodoInicial,_edge_id,GML_ID_INICIO,Inicio_z,PSRoomType,gml_name{0},usage,xlink_href,gml_metaDataProperty{0}.nilReason,class,Inicio_y,duality.xlink_href,partialboundedBy{0}.xlink_href,Fin_x,partialboundedBy{0}.nilReason,citygml_address{0}.xlink_href,GML_ID_FINAL,Inicio_x,duality.nilReason,Face_list{0}.NodoFinal,Fin_z,Fin_y,function
    -> Transition
Transition: Logger
    LOG_FEATURE = LOG_ONLY
    MAXCOORDS = 20
    MAXFEATS = 20
    MESSAGE = Feature is:
    SEVERITY = INFO
    LOGGED -> Transition (writer INDOORGML_1)

Bookmark: -partialboundedBy_Door-limites Door
Note: Identifica y asigna todos los atrubitos de los limites de Door a la derecha
FeatureJoiner_3
    ATTR_CONFLICT_RES = Use Left
    GEOMETRY_HANDLING = Use Left
    JOIN_KEYS = Face_list{0}.gml_id gml_id AUTO
    JOIN_MODE = Inner
    JOINED -> AttributeCreator_5
FeatureJoiner_4
    ATTR_CONFLICT_RES = Use Left
    GEOMETRY_HANDLING = Use Left
    JOIN_KEYS = Face_list{1}.gml_id gml_id AUTO
    JOIN_MODE = Inner
    JOINED -> AttributeCreator_5
AttributeCreator_5
    ATTR_TABLE:
      SET_TO gml_id1 = @Value(Face_list{0}.gml_id)_vs_@Value(Face_list{1}.gml_id)_REVERSE
      SET_TO xlink_href = #@Value(gml_id1)
    -> ListBuilder
    -> FeatureJoiner_9 [RIGHT]
Note: Lista de los límites que definen un espacio de conexión, Door
ListBuilder
    GROUP_BY = gml_id
    LIST_ATTRS_TO_INCLUDE = xlink_href
    LIST_NAME = partialboundedBy
    -> FeatureJoiner_5 [RIGHT]
Note: Union de la lista con elementogeometrico Door
FeatureJoiner_5
    ATTR_CONFLICT_RES = Use Left
    GEOMETRY_HANDLING = Use Left
    JOIN_KEYS = gml_id gml_id AUTO
    JOIN_MODE = Inner
    JOINED -> AttributeCreator_13
    JOINED -> CenterPointReplacer

Bookmark: State
AttributeCreator_13
    ATTR_TABLE:
      SET_TO gml_id0 = S_@Value(gml_id)
      SET_TO duality.xlink_href = #@Value(gml_id0)
    -> Connection_Space
Connection_Space: Logger
    LOG_FEATURE = LOG_ONLY
    MAXCOORDS = 20
    MAXFEATS = 20
    MESSAGE = Feature is:
    SEVERITY = INFO
    LOGGED -> ConnectionSpace (writer INDOORGML_1)

Bookmark: State
CenterPointReplacer
    POINTTYPE = CENTER
    POINT -> AttributeCreator_4
CenterPointReplacer_2
    POINTTYPE = CENTER
    POINT -> AttributeCreator_4
AttributeCreator_4
    ATTR_TABLE:
      SET_TO gml_parent_id = N_SL_SLs_MG_IF_500
      SET_TO gml_parent_property = stateMember
      SET_TO gml_id0 = @Value(gml_id)
      SET_TO gml_id = S_@Value(gml_id)
      SET_TO duality.xlink_href = #@Value(gml_id0)
    -> State
State: Logger
    LOG_FEATURE = LOG_ONLY
    MAXCOORDS = 20
    MAXFEATS = 20
    MESSAGE = Feature is:
    SEVERITY = INFO
    LOGGED -> State (writer INDOORGML_1)
    LOGGED -> FeatureJoiner_12 [LEFT]
    LOGGED -> FeatureJoiner_11 [LEFT]

Bookmark: -partialboundedBy_limites Room
FeatureJoiner_6
    ATTR_CONFLICT_RES = Use Left
    GEOMETRY_HANDLING = Use Left
    JOIN_KEYS = Face_list{0}.gml_id gml_id AUTO
    JOIN_MODE = Inner
    JOINED -> AttributeCreator_11
FeatureJoiner_7
    ATTR_CONFLICT_RES = Use Left
    GEOMETRY_HANDLING = Use Left
    JOIN_KEYS = Face_list{1}.gml_id gml_id AUTO
    JOIN_MODE = Inner
    JOINED -> AttributeCreator_11
AttributeCreator_11
    ATTR_TABLE:
      SET_TO gml_id1 = @Value(Face_list{0}.gml_id)_vs_@Value(Face_list{1}.gml_id)_REVERSE
      SET_TO xlink_href = #@Value(gml_id1)
    -> ListBuilder_3
    -> FeatureJoiner_9 [RIGHT]
ListBuilder_3
    GROUP_BY = gml_id
    LIST_ATTRS_TO_INCLUDE = xlink_href
    LIST_NAME = partialboundedBy
    -> FeatureJoiner_8 [RIGHT]
FeatureJoiner_8
    ATTR_CONFLICT_RES = Use Left
    GEOMETRY_HANDLING = Use Left
    JOIN_KEYS = gml_id gml_id AUTO
    JOIN_MODE = Inner
    JOINED -> CenterPointReplacer_2
    JOINED -> AttributeCreator_14
    UNJOINED_LEFT -> CenterPointReplacer_2
    UNJOINED_LEFT -> AttributeCreator_14

Bookmark: GeneralSpace
AttributeCreator_14
    ATTR_TABLE:
      SET_TO gml_id0 = S_@Value(gml_id)
      SET_TO duality.xlink_href = #@Value(gml_id0)
      SET_TO tipoSpace = @Value(gml_tipo)
    -> AttributeFilter_3
AttributeFilter_3
    ATTR_NAME = tipoSpace
    ATTR_VALUES = <Empty>,<Missing>,<Null>,<Unfiltered>,Transito,General
    Transito -> AppearanceSetter_7 [GEOMETRY]
    General -> AppearanceSetter_2 [GEOMETRY]
AppearanceSetter_7
    ALPHA = 0.5
    DEF_STORAGE = Create New Definitions
    DIFFUSE_COLOR = 0,1,0.498039
    EMISSIVE_COLOR = 0.901961,0.901961,0.901961
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    TEXTURE_WRAP_DISPLAY = Mirror
    USE_EXISTING_TEXTURE_COORDINATES = No
    -> TransitionSpace
TransitionSpace: Logger
    LOG_FEATURE = LOG_ONLY
    MAXCOORDS = 20
    MAXFEATS = 20
    MESSAGE = Feature is:
    SEVERITY = INFO
    LOGGED -> TransitionSpace (writer INDOORGML_1)
AppearanceSetter_2
    ALPHA = 0.5
    DEF_STORAGE = Create New Definitions
    DIFFUSE_COLOR = 0.333333,0.666667,1
    EMISSIVE_COLOR = 0.901961,0.901961,0.901961
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    TEXTURE_WRAP_DISPLAY = Mirror
    USE_EXISTING_TEXTURE_COORDINATES = No
    -> GeneralSpace
GeneralSpace: Logger
    LOG_FEATURE = LOG_ONLY
    MAXCOORDS = 20
    MAXFEATS = 20
    SEVERITY = INFO
    LOGGED -> GeneralSpace (writer INDOORGML_1)

Bookmark: ConnectionBoundary
FeatureJoiner_9
    ATTR_CONFLICT_RES = Use Left
    GEOMETRY_HANDLING = Use Left
    JOIN_KEYS = _edge_id _edge_id AUTO
    JOIN_MODE = Inner
    JOINED -> AttributeRemover_6
AttributeRemover_6
    REMOVE_ATTRS = citygml_address{3}.xlink_href,citygml_address{7}.xlink_href,gml_id,citygml_address{8}.xlink_href,citygml_address{4}.xlink_href,_edge_id,partialboundedBy{0}.nilReason,duality.nilReason,xlink_href,class,usage,gml_description,gml_metaDataProperty{0}.nilReason,citygml_address{6}.xlink_href,PSRoomType,citygml_address{0}.xlink_href,citygml_address{5}.xlink_href,gml_name,citygml_address{1}.xlink_href,gml_parent_property,citygml_address{9}.xlink_href,function,citygml_address{2}.xlink_href,citygml_address{10}.xlink_href,gml_id0
    -> AttributeCreator_12
AttributeCreator_12
    ATTR_TABLE:
      SET_TO gml_parent_property = cellSpaceBoundaryMember
      SET_TO gml_id = @Value(gml_id1)
      SET_TO xml_ns_uri = http://www.opengis.net/indoorgml/1.0/navigation
    -> ConnectionBoundary
ConnectionBoundary: Logger
    LOG_FEATURE = LOG_ONLY
    MAXCOORDS = 20
    MAXFEATS = 20
    MESSAGE = Feature is:
    SEVERITY = INFO
    LOGGED -> ConnectionBoundary (writer INDOORGML_1)

Bookmark: New Bookmark
Note: Identifica y asigna todos los atrubitos de los limites de Door a la izquierda
Note: Union de la lista con elementogeometrico Room
