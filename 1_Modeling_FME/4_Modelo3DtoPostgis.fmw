FME workspace 4_Modelo3DtoPostgis.fmw

Parameters:
- DestDataset_POSTGIS =
- SourceDataset_CITYGML =
- SourceDataset_INDOORGML_3 =

Readers:
- INDOORGML_1: INDOORGML from $(SourceDataset_INDOORGML_3)
- CITYGML_1: CITYGML from $(SourceDataset_CITYGML)

Writers:
- POSTGIS_1: POSTGIS to $(DestDataset_POSTGIS)

Bookmark: Clases de entrada
State (reader INDOORGML_1)
    attributes: nilReason xml_buffer, gml_remoteSchema xml_buffer, xlink_href xml_buffer, xlink_role xml_buffer, xlink_title xml_buffer, duality.nilReason xml_buffer, duality.gml_remoteSchema xml_buffer, duality.xlink_href xml_buffer, duality.xlink_role xml_buffer, duality.xlink_title xml_buffer, connects{}.nilReason xml_buffer, connects{}.gml_remoteSchema xml_buffer, connects{}.xlink_href xml_buffer, connects{}.xlink_role xml_buffer, connects{}.xlink_title xml_buffer, geometry xml_geometry
    -> Counter
Transition (reader INDOORGML_1)
    attributes: nilReason xml_buffer, gml_remoteSchema xml_buffer, xlink_href xml_buffer, xlink_role xml_buffer, xlink_title xml_buffer, weight xml_real64, connects{}.nilReason xml_buffer, connects{}.gml_remoteSchema xml_buffer, connects{}.xlink_href xml_buffer, connects{}.xlink_role xml_buffer, connects{}.xlink_title xml_buffer, duality.nilReason xml_buffer, duality.gml_remoteSchema xml_buffer, duality.xlink_href xml_buffer, duality.xlink_role xml_buffer, duality.xlink_title xml_buffer, geometry xml_geometry
    -> FeatureJoiner [LEFT]
Room (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, citygml_interior_furniture{}.xlink_href xml_buffer, citygml_room_installation{}.xlink_href xml_buffer, gml_tipo xml_buffer
    -> AttributeRemover_2
Door (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_address{}.xlink_href xml_buffer, tipo xml_buffer
    -> AttributeRemover_3

Bookmark: Tranformadores
Counter
    CNT_ATTR = gid
    DOMAIN = counter
    SCOPE = Global
    START = 1
    -> state (writer POSTGIS_1)
    -> FeatureJoiner [RIGHT]
    -> FeatureJoiner_2 [RIGHT]
FeatureJoiner
    ATTR_CONFLICT_RES = Use Left
    GEOMETRY_HANDLING = Use Left
    JOIN_KEYS = connects{0}.xlink_href gml_id AUTO
    JOIN_MODE = Left
    JOINED -> AttributeCreator_2
AttributeCreator_2
    ATTR_TABLE = SET_TO source = @Value(gid)
    -> AttributeRemover
AttributeRemover
    REMOVE_ATTRS = nilReason,gid
    -> FeatureJoiner_2 [LEFT]
FeatureJoiner_2
    ATTR_CONFLICT_RES = Use Left
    GEOMETRY_HANDLING = Use Left
    JOIN_KEYS = connects{1}.xlink_href gml_id AUTO
    JOIN_MODE = Left
    JOINED -> AttributeCreator_3
AttributeCreator_3
    ATTR_TABLE = SET_TO target = @Value(gid)
    -> transition (writer POSTGIS_1)
AttributeRemover_2
    REMOVE_ATTRS = citygml_appearance{0}.xlink_href,citygml_bounded_by{0}.xlink_href,citygml_class,citygml_class_codeSpace,citygml_creationDate,citygml_feature_role,citygml_feature_role_attr_name,citygml_feature_role_attr_val,citygml_function{0},citygml_function{0}.codeSpace,citygml_generalizes_to{0}.xlink_href,citygml_interior_furniture{0}.xlink_href,citygml_level_of_detail{0},citygml_relative_to_terrain,citygml_relative_to_water,citygml_room_installation{0}.xlink_href,citygml_target_uri,citygml_terminationDate,citygml_usage{0},citygml_usage{0}.codeSpace,externalReference{0}.externalObject.name,externalReference{0}.externalObject.uri,externalReference{0}.informationSystem,gml_tipo
    -> room (writer POSTGIS_1)
AttributeRemover_3
    REMOVE_ATTRS = citygml_address{0}.xlink_href,citygml_appearance{0}.xlink_href,citygml_creationDate,citygml_feature_role,citygml_feature_role_attr_name,citygml_feature_role_attr_val,citygml_generalizes_to{0}.xlink_href,citygml_level_of_detail{0},citygml_relative_to_terrain,citygml_relative_to_water,citygml_target_uri,citygml_terminationDate,externalReference{0}.externalObject.name,externalReference{0}.externalObject.uri,externalReference{0}.informationSystem,tipo
    -> door (writer POSTGIS_1)

Bookmark: Resultado
state (writer POSTGIS_1)
    attributes: gml_parent_id text, gml_parent_property text, xlink_href text, gml_id text,BTree, gid float4,PrimaryKey
transition (writer POSTGIS_1)
    attributes: gml_parent_id text, gml_parent_property text, gml_id text,PrimaryKey, source int4,BTree, target int4,BTree
room (writer POSTGIS_1)
    attributes: gml_id text,PrimaryKey, gml_parent_id text, gml_description text,BTree, gml_name text,BTree
door (writer POSTGIS_1)
    attributes: gml_id text,PrimaryKey, gml_parent_id text, gml_description text,BTree, gml_name text,BTree
